MY-MIB DEFINITIONS ::= BEGIN

IMPORTS
    DisplayString
        FROM SNMPv2-TC
    Counter64, Gauge32, Integer32, OBJECT IDENTIFIER
        FROM SNMPv2-SMI;

MY-MIB MODULE-IDENTITY
    LAST-UPDATED "202501110000Z"
    ORGANIZATION "My Organization"
    CONTACT-INFO "Contact Info"
    DESCRIPTION "Example MIB generated from CSV"
    REVISION "202501110000Z"
    DESCRIPTION "Initial version"
    ::= { 1.3.6.1.4.1.9999 }

myEnumVal ::= INTEGER {
    red(1),
    green(2),
    blue(3)
}

myTableEntry ::= SEQUENCE {
    myTableIndex    Integer32,
    myTableValue    DisplayString
}

myString OBJECT-TYPE
    SYNTAX      DisplayString
    MAX-ACCESS  read-only
    STATUS      current
    DESCRIPTION
        "An example string"
    ::= { MY-MIB 1 }

myInteger OBJECT-TYPE
    SYNTAX      Integer32
    MAX-ACCESS  read-write
    STATUS      current
    DESCRIPTION
        "An example integer"
    ::= { MY-MIB 2 }

myEnum OBJECT-TYPE
    SYNTAX      myEnumVal
    MAX-ACCESS  read-only
    STATUS      current
    DESCRIPTION
        "An example enumeration"
    ::= { MY-MIB 3 }

myGauge OBJECT-TYPE
    SYNTAX      Gauge32
    MAX-ACCESS  read-only
    STATUS      current
    DESCRIPTION
        "An example gauge"
    ::= { MY-MIB 4 }

myCounter OBJECT-TYPE
    SYNTAX      Counter64
    MAX-ACCESS  read-only
    STATUS      current
    DESCRIPTION
        "An example counter"
    ::= { MY-MIB 5 }

myTable OBJECT-TYPE
    SYNTAX      SEQUENCE
    MAX-ACCESS  not-accessible
    STATUS      current
    DESCRIPTION
        "An example table"
    ::= { MY-MIB 6 }

myTableEntry OBJECT-TYPE
    SYNTAX      OBJECT IDENTIFIER
    MAX-ACCESS  not-accessible
    STATUS      current
    DESCRIPTION
        "An example table entry"
    INDEX      { myTableIndex }
    ::= { myTable 1 }

myTableIndex OBJECT-TYPE
    SYNTAX      Integer32
    MAX-ACCESS  read-only
    STATUS      current
    DESCRIPTION
        "Index for the table"
    ::= { myTableEntry 1 }

myTableValue OBJECT-TYPE
    SYNTAX      DisplayString
    MAX-ACCESS  read-write
    STATUS      current
    DESCRIPTION
        "Value in the table"
    ::= { myTableEntry 2 }

END
